FME workspace CreateTaskTicket_old.fmw

Parameters:
- server_work = a4pa-db-work.infra.be.ch/a4phwork   # Server Work
- pw_gpdb =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   # PW gdbp
- User_gdbp = gdbp   # User gdbp
- server_team = teamp   # Server Team
- PW_geodb_dd =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   # PW GeoDB_DD
- User_geodb_dd = geodb_dd   # User GeoDB_DD
- Quelle_TEAM = teamp   # Source Oracle Non-spatial Service
- Ziel_TEAM = teamp   # Destination Oracle Non-spatial Service
- OEREB_GPR = NPL,NPLWALD,NPLKUEO,NPLKSTRA,KBSOEV,KBSFLUG,PRJZFLUG,SIZOPLAN,BALISKBS,GSK25   # ÖREB-Geoprodukte
- OEREB_DATABASE = a4pa-db-work.infra.be.ch/a4phwork   # ÖREB-Database
- OEREB_USERNAME = oereb   # ÖREB-Username
- OEREB_PASSWORD =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   # ÖREB-Passwort
- DestDataset_ORACLE8I_DB = a4pa-db-work.infra.be.ch/a4phwork   # Destination Oracle Non-spatial Service
- gzs_objectid =

Readers:
- ORACLE8I_DB_1: ORACLE8I_DB from $(Quelle_TEAM)

Writers:
- ORACLE8I_DB_2: ORACLE8I_DB to $(Ziel_TEAM)
- ORACLE8I_DB_3: ORACLE8I_DB to $(DestDataset_ORACLE8I_DB)

Note: Ausgabe aller freigegebenen / Geoproduktzeitstände in GeoDBprozess / - Freigabedatum Normierung erfasst / - Startdatum Import offen
SQLCreator_gdbp
    ORACLE8I_DB_USER_NAME = $(User_gdbp)
    ORACLE8I_DB_SHOW_SYSTEM_TABLES = NO
    ORACLE8I_DB_PASSWORD = $(pw_gpdb)
    SQL_STATEMENT:
      select t.code,
             t.title,
             t.zeitstand_jahr,
             t.zeitstand_version,
             t.id_gp_fall,
             t.gewuenschtes_wippendatum
        from gdbp.geoprodukte t
       where t.freigabedatum_normierung is not Null
         and t.arbeitstartdatum_import is Null
       order by t.code asc
    EXPOSED_ATTRIBUTE_LIST = CODE,GEWUENSCHTES_WIPPENDATUM,GEWUENSCHTES_WIPPENDATUM.full,ID_GP_FALL,TITLE,ZEITSTAND_JAHR,ZEITSTAND_VERSION
    ORACLE8I_DB_SERVER_TYPE = ORACLE8i
    DATASET = $(server_work)
    ORACLE8I_DB_REMOVE_SCHEMA_QUALIFIER = NO
    ORACLE8I_DB_PERSISTENT_CONNECTION = YES
    FORMAT = ORACLE8I_DB
    RESULT -> FeatureMerger_gzs_objectid [input 2]
    RESULT -> FeatureMerger_fall [input 1]
Note: Ausgabe des / Geoproduktzeitstand (Status = 1 and / gzs_objectid) / aus GeoDB_DD
SQLCreator_geodb_dd_gzs
    ORACLE8I_DB_USER_NAME = $(User_geodb_dd)
    ORACLE8I_DB_SHOW_SYSTEM_TABLES = NO
    ORACLE8I_DB_PASSWORD = $(PW_geodb_dd)
    SQL_STATEMENT:
      SELECT a.gzs_objectid,
        b.gpr_bezeichnung,
        a.gzs_jahr,
        a.gzs_version
      FROM geodb_dd.tb_geoprodukt_zeitstand a
      JOIN geodb_dd.tb_geoprodukt b
      ON a.gpr_objectid    = b.gpr_objectid
      WHERE a.sta_objectid = 1
          and a.gzs_objectid = $(gzs_objectid)
    EXPOSED_ATTRIBUTE_LIST = GPR_BEZEICHNUNG,GZS_JAHR,GZS_OBJECTID,GZS_VERSION
    ORACLE8I_DB_SERVER_TYPE = ORACLE8i
    DATASET = $(server_team)
    ORACLE8I_DB_REMOVE_SCHEMA_QUALIFIER = NO
    ORACLE8I_DB_PERSISTENT_CONNECTION = YES
    FORMAT = ORACLE8I_DB
    RESULT -> FeatureMerger_gzs_objectid [input 1]
    RESULT -> FeatureMerger_fall [input 1]
Note: gzs_objectid aus GeoDB_DD / der in GeoDBprozess / freigegebenen Geoprodukte
FeatureMerger_gzs_objectid
    PROCESS_DUPS = No
    MERGE_TYPE = Attributes Only
    SUPPLIERS_FIRST = No
    JOIN_KEYS = @Value(GPR_BEZEICHNUNG) @Value(CODE) AUTO @Value(GZS_JAHR) @Value(ZEITSTAND_JAHR) AUTO @Value(GZS_VERSION) @Value(ZEITSTAND_VERSION) AUTO
    SUPPLIER_PREFIX_DUMMY = YES
    MERGED -> FeatureMerger_fall [input 1]
Note: geodb_dd.tb_usecase
SQLCreator_geodb_dd_uc
    ORACLE8I_DB_USER_NAME = $(User_geodb_dd)
    ORACLE8I_DB_SHOW_SYSTEM_TABLES = NO
    ORACLE8I_DB_PASSWORD = $(PW_geodb_dd)
    SQL_STATEMENT = SELECT a.* from geodb_dd.tb_usecase a
    EXPOSED_ATTRIBUTE_LIST = UC_BEZEICHNUNG,UC_DMA,UC_OBJECTID,UC_STARTSTATUS
    ORACLE8I_DB_SERVER_TYPE = ORACLE8i
    DATASET = $(server_team)
    ORACLE8I_DB_REMOVE_SCHEMA_QUALIFIER = NO
    ORACLE8I_DB_PERSISTENT_CONNECTION = YES
    FORMAT = ORACLE8I_DB
    RESULT -> AttributeRenamer
AttributeRenamer
    ATTR_LIST = UC_STARTSTATUS,TASK_STATUS,""
    -> FeatureMerger_fall [input 2]
Note: uc_objectid aus GeoDB_DD / für Fall in GeoDBprozess
FeatureMerger_fall
    PROCESS_DUPS = No
    MERGE_TYPE = Attributes Only
    SUPPLIERS_FIRST = No
    JOIN_KEYS = @Value(ID_GP_FALL) @Value(UC_OBJECTID) NUM
    SUPPLIER_PREFIX_DUMMY = YES
    MERGED -> FeatureMerger_2 [input 1]
Note: geodb_dd.tb_task
GEODB_DD.TB_TASK (reader ORACLE8I_DB_1)
    attributes: TASK_OBJECTID number(38,0), GZS_OBJECTID number(38,0), UC_OBJECTID number(38,0), TASK_SERVER varchar2(100), TASK_STATUS number(38,0), TASK_START date, TASK_ENDE date
    -> FeatureMerger_2 [input 2]
Note: WARNING: nicht synchronisiert werden nur gzs_objectids, welche mehr als einmal korrigiert werden
Note: Filter, ob gzs_objectid mit / demselben UC bereits vorkommt
FeatureMerger_2
    PROCESS_DUPS = No
    MERGE_TYPE = Attributes Only
    SUPPLIERS_FIRST = No
    JOIN_KEYS = @Value(GZS_OBJECTID) @Value(GZS_OBJECTID) NUM @Value(ID_GP_FALL) @Value(UC_OBJECTID) AUTO
    SUPPLIER_PREFIX_DUMMY = YES
    NOT_MERGED -> SQLExecutor
Note: TASK_OBJECTID aus der Sequenz / holen.
SQLExecutor
    ORACLE8I_DB_USER_NAME = $(User_geodb_dd)
    ORACLE8I_DB_SHOW_SYSTEM_TABLES = NO
    ORACLE8I_DB_PASSWORD = $(PW_geodb_dd)
    SQL_STATEMENT = select GDBBE_SEQ.NEXTVAL as TASK_OBJECTID FROM dual
    EXPOSED_ATTRIBUTE_LIST = TASK_OBJECTID
    ORACLE8I_DB_SERVER_TYPE = ORACLE8i
    DATASET = $(Ziel_TEAM)
    ORACLE8I_DB_REMOVE_SCHEMA_QUALIFIER = NO
    ORACLE8I_DB_PERSISTENT_CONNECTION = YES
    COMBINE_GEOM = Initiator Geometry Only
    COMBINE_ATTRS = Keep Initiator Attributes if Conflict
    FORMAT = ORACLE8I_DB
    RESULT -> PythonCaller
Note: Ermitteln, ob es sich um ein ÖREB- / Geoprodukt handelt oder nicht. / Die Codes der ÖREB-Geoprodukte / sind im Parameter OEREB_GPR / definiert.
PythonCaller
    PYTHONSOURCE:
      import fmeobjects

      def processFeature(feature):
          oereb_gpr_string = FME_MacroValues['OEREB_GPR']
          oereb_gpr_list = oereb_gpr_string.split(',')
          oereb_gpr_list = [x.upper() for x in oereb_gpr_list]
          gpr_status = "NORMAL"
          gprcode = feature.getAttribute('GPR_BEZEICHNUNG').upper()
          if gprcode in oereb_gpr_list:
              gpr_status = 'OEREB'

          feature.setAttribute('GPR_STATUS', gpr_status)
    PYTHONSYMBOL = processFeature
    NEW_ATTRIBUTES = GPR_STATUS
    -> AttributeRemover
AttributeRemover
    REMOVE_ATTRS = CODE,GEWUENSCHTES_WIPPENDATUM,GEWUENSCHTES_WIPPENDATUM.full,ID_GP_FALL,TITLE,ZEITSTAND_JAHR,ZEITSTAND_VERSION,GZS_JAHR,GZS_VERSION,UC_BEZEICHNUNG,UC_DMA
    -> TestFilter
Note: Testen auf ÖREB-Geoprodukt oder nicht. / Tasks für normale Geoprodukte werden / direkt in TB_TASK geschrieben. / Tasks von ÖREB-Geoprodukten werden ebenfalls in TB_TASK geschrieben. Zusätzlich wird jedoch die TASK_OBJECTID in die ÖREB-Tickettabelle geschrieben.
TestFilter
    TEST_LIST = BOOL_OP,OR,COMPOSITE_TEST,<Unused>,TEST_CLAUSE,"TEST @Value(GPR_STATUS) = OEREB",OEREB
    DEFAULT_VALUE = NORMAL
    OEREB -> SQLExecutor_2
    NORMAL -> AttributeRemover_4
Note: Zugehörige Ticket-ID des ÖREB-Katasters ermitteln. In Frage kommen nur Tickets mit: / ART=4 (Aktualisierung mit Zeitstand) / STATUS=4 (freigegeben) / TASK_ID_GEODB is null (noch keine TASK_ID eingetragen)
SQLExecutor_2
    ORACLE8I_DB_USER_NAME = $(OEREB_USERNAME)
    ORACLE8I_DB_SHOW_SYSTEM_TABLES = NO
    ORACLE8I_DB_PASSWORD = $(OEREB_PASSWORD)
    SQL_STATEMENT = select ticket.id as oereb_ticket_id from ticket left join liefereinheit on ticket.LIEFEREINHEIT=liefereinheit.ID where ticket.art=4 and ticket.status=4 and ticket.TASK_ID_GEODB is null and liefereinheit.GPRCODE='@Value(GPR_BEZEICHNUNG)'
    EXPOSED_ATTRIBUTE_LIST = OEREB_TICKET_ID
    ORACLE8I_DB_SERVER_TYPE = ORACLE8i
    DATASET = $(OEREB_DATABASE)
    ORACLE8I_DB_REMOVE_SCHEMA_QUALIFIER = NO
    ORACLE8I_DB_PERSISTENT_CONNECTION = YES
    COMBINE_GEOM = Initiator Geometry Only
    COMBINE_ATTRS = Keep Initiator Attributes if Conflict
    FORMAT = ORACLE8I_DB
    RESULT -> StringConcatenator
    INITIATOR -> TestFilter_2
StringConcatenator
    PARM_LINE = ID=@Value(OEREB_TICKET_ID)
    VAL_ATTR = fme_where
    -> AttributeRemover_2
AttributeRemover_2
    REMOVE_ATTRS = GPR_BEZEICHNUNG,GZS_OBJECTID,UC_OBJECTID,TASK_STATUS,GPR_STATUS,OEREB_TICKET_ID
    -> AttributeRenamer_2
AttributeRenamer_2
    ATTR_LIST = TASK_OBJECTID,TASK_ID_GEODB,""
    -> OEREB.TICKET (writer ORACLE8I_DB_3)
Note: OEREB.TICKET (Update)
OEREB.TICKET (writer ORACLE8I_DB_3)
    attributes: TASK_ID_GEODB number(38,0)
TestFilter_2
    TEST_LIST = BOOL_OP,OR,COMPOSITE_TEST,<Unused>,TEST_CLAUSE,"TEST @Value(_matched_records) = 0",NO_TICKET
    DEFAULT_VALUE = TICKET_FOUND
    NO_TICKET -> TestFilter_2_NO_TICKET
    TICKET_FOUND -> AttributeRemover_5
Note: Alle Tasks, für die kein ÖREB-Ticket gefunden wurde, werden hier geloggt.Sie werden auch nicht in TB_TASK geschrieben. Dies geschieht erst, wenn es ein dazugehöriges Ticket gibt.
TestFilter_2_NO_TICKET: Logger
    MESSAGE = Für folgende Tasks konnte kein ÖREB-Ticket gefunden werden:
    MAXFEATS = 50
    MAXCOORDS = 20
AttributeRemover_5
    REMOVE_ATTRS = GPR_BEZEICHNUNG,GPR_STATUS,_matched_records
    -> GEODB_DD.TB_TASK (writer ORACLE8I_DB_2)
AttributeRemover_4
    REMOVE_ATTRS = GPR_BEZEICHNUNG,GPR_STATUS
    -> GEODB_DD.TB_TASK (writer ORACLE8I_DB_2)
Note: insert tb_task from GeoDBprozess
GEODB_DD.TB_TASK (writer ORACLE8I_DB_2)
    attributes: TASK_OBJECTID number(38,0), GZS_OBJECTID number(38,0), UC_OBJECTID number(38,0), TASK_SERVER varchar2(100), TASK_STATUS number(38,0), TASK_START date, TASK_ENDE date
