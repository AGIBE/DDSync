FME workspace CreateTaskTicket.fmw

Parameters:
- database_work =   # Server Work
- pw_gpdb =   # PW gdbp
- User_gdbp =   # User gdbp
- PW_geodb_dd =   # PW GeoDB_DD
- User_geodb_dd =   # User GeoDB_DD
- database_team =   # Source Oracle Non-spatial Service
- OEREB_GPR =   # ÖREB-Geoprodukte
- OEREB_DATABASE =   # ÖREB-Database
- OEREB_USERNAME =   # ÖREB-Username
- OEREB_PASSWORD =   # ÖREB-Passwort
- OEREB_HOST =
- OEREB_PORT =
- LOGFILE = \\geodb-bkt.infra.be.ch\freigabe\Anwendungen\DDSync\log\test.log

Readers:
- ORACLE8I_DB_1: ORACLE8I_DB from $(database_team)

Writers:
- ORACLE8I_DB_2: ORACLE8I_DB to $(database_team)
- POSTGRES_1: POSTGRES to $(OEREB_DATABASE)

Note: Ausgabe aller freigegebenen / Geoproduktzeitstände in GeoDBprozess / - Freigabedatum Normierung erfasst / - Startdatum Import offen
SQLCreator_gdbp
    DATASET = $(database_work)
    EXPOSED_ATTRIBUTE_LIST = CODE,GEWUENSCHTES_WIPPENDATUM,GEWUENSCHTES_WIPPENDATUM.full,ID_GP_FALL,TITLE,ZEITSTAND_JAHR,ZEITSTAND_VERSION
    FORMAT = ORACLE8I_DB
    ORACLE8I_DB_PASSWORD = $(pw_gpdb)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(User_gdbp)
    ORACLE8I_DB_USE_UNIFIED_DATE_ATTRS = YES
    SQL_STATEMENT:
      select t.code,
             t.title,
             t.zeitstand_jahr,
             t.zeitstand_version,
             t.id_gp_fall,
             t.gewuenschtes_wippendatum
        from gdbp.geoprodukte t
       where t.freigabedatum_normierung is not Null
         and t.arbeitstartdatum_import is Null
       order by t.code asc
    RESULT -> FeatureMerger_gzsobjectid [REQUESTOR]
Note: Ausgabe aller angelegten / Geoproduktzeitstände (Status = 1) / aus GeoDB_DD
SQLCreator_geodb_dd_gzs
    DATASET = $(database_team)
    EXPOSED_ATTRIBUTE_LIST = GPR_BEZEICHNUNG,GZS_JAHR,GZS_OBJECTID,GZS_VERSION
    FORMAT = ORACLE8I_DB
    ORACLE8I_DB_PASSWORD = $(PW_geodb_dd)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(User_geodb_dd)
    ORACLE8I_DB_USE_UNIFIED_DATE_ATTRS = YES
    SQL_STATEMENT:
      SELECT a.gzs_objectid,
        b.gpr_bezeichnung,
        a.gzs_jahr,
        a.gzs_version
      FROM geodb_dd.tb_geoprodukt_zeitstand a
      JOIN geodb_dd.tb_geoprodukt b
      ON a.gpr_objectid    = b.gpr_objectid
      WHERE a.sta_objectid = 1
    RESULT -> FeatureMerger_gzsobjectid [SUPPLIER]
Note: gzs_objectid aus GeoDB_DD / der in GeoDBprozess / freigegebenen Geoprodukte
FeatureMerger_gzsobjectid
    ATTR_ACCUM_MODE = Merge Supplier
    ATTR_CONFLICT_RES = Use Requestor
    IGNORE_NULLS = Yes
    JOIN_KEYS = @Value(CODE) @Value(GPR_BEZEICHNUNG) STRING @Value(ZEITSTAND_JAHR) @Value(GZS_JAHR) NUM @Value(ZEITSTAND_VERSION) @Value(GZS_VERSION) STRING
    MERGE_TYPE = Attributes Only
    PROCESS_DUPS = No
    REJECT_NULL_MISSING_KEYS = No
    SUPPLIERS_FIRST = No
    MERGED -> FeatureMerger_fall [REQUESTOR]
Note: geodb_dd.tb_usecase
SQLCreator_geodb_dd_uc
    DATASET = $(database_team)
    EXPOSED_ATTRIBUTE_LIST = UC_BEZEICHNUNG,UC_DMA,UC_OBJECTID,UC_STARTSTATUS
    FORMAT = ORACLE8I_DB
    ORACLE8I_DB_PASSWORD = $(PW_geodb_dd)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(User_geodb_dd)
    ORACLE8I_DB_USE_UNIFIED_DATE_ATTRS = YES
    SQL_STATEMENT = SELECT a.* from geodb_dd.tb_usecase a
    RESULT -> AttributeRenamer
AttributeRenamer
    ATTR_TABLE = RENAME_SET_DEFAULT UC_STARTSTATUS > TASK_STATUS
    -> FeatureMerger_fall [SUPPLIER]
Note: uc_objectid aus GeoDB_DD / für Fall in GeoDBprozess
FeatureMerger_fall
    ATTR_ACCUM_MODE = Merge Supplier
    ATTR_CONFLICT_RES = Use Requestor
    IGNORE_NULLS = Yes
    JOIN_KEYS = @Value(ID_GP_FALL) @Value(UC_OBJECTID) NUM
    MERGE_TYPE = Attributes Only
    PROCESS_DUPS = No
    REJECT_NULL_MISSING_KEYS = No
    SUPPLIERS_FIRST = No
    MERGED -> FeatureMerger_2 [REQUESTOR]
Note: geodb_dd.tb_task
TB_TASK (reader ORACLE8I_DB_1)
    attributes: TASK_OBJECTID number(38,0), GZS_OBJECTID number(38,0), UC_OBJECTID number(38,0), TASK_SERVER varchar2(100), TASK_STATUS number(38,0), TASK_START date, TASK_ENDE date
    -> FeatureMerger_2 [SUPPLIER]
Note: WARNING: nicht synchronisiert werden nur gzs_objectids, welche mehr als einmal korrigiert werden
Note: Filter, ob gzs_objectid mit / demselben UC bereits vorkommt
FeatureMerger_2
    ATTR_ACCUM_MODE = Merge Supplier
    ATTR_CONFLICT_RES = Use Requestor
    IGNORE_NULLS = Yes
    JOIN_KEYS = @Value(GZS_OBJECTID) @Value(GZS_OBJECTID) NUM @Value(ID_GP_FALL) @Value(UC_OBJECTID) AUTO
    MERGE_TYPE = Attributes Only
    PROCESS_DUPS = No
    REJECT_NULL_MISSING_KEYS = No
    SUPPLIERS_FIRST = No
    NOT_MERGED -> SQLExecutor [INITIATOR]
Note: TASK_OBJECTID aus der Sequenz / holen.
SQLExecutor
    COMBINE_ATTRS = Keep Initiator Attributes if Conflict
    COMBINE_GEOM = Initiator Geometry Only
    DATASET = $(database_team)
    EXPOSED_ATTRIBUTE_LIST = TASK_OBJECTID
    FORMAT = ORACLE8I_DB
    ORACLE8I_DB_PASSWORD = $(PW_geodb_dd)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(User_geodb_dd)
    ORACLE8I_DB_USE_UNIFIED_DATE_ATTRS = YES
    SQL_STATEMENT = select GDBBE_SEQ.NEXTVAL as TASK_OBJECTID FROM dual
    RESULT -> PythonCaller
Note: Ermitteln, ob es sich um ein ÖREB- / Geoprodukt handelt oder nicht. / Die Codes der ÖREB-Geoprodukte / sind im Parameter OEREB_GPR / definiert.
PythonCaller
    NEW_ATTRIBUTES = GPR_STATUS
    PYTHONSOURCE:
      import fmeobjects

      def processFeature(feature):
          oereb_gpr_string = FME_MacroValues['OEREB_GPR']
          oereb_gpr_list = oereb_gpr_string.split(',')
          oereb_gpr_list = [x.upper() for x in oereb_gpr_list]
          gpr_status = "NORMAL"
          gprcode = feature.getAttribute('GPR_BEZEICHNUNG').upper()
          if gprcode in oereb_gpr_list:
              gpr_status = 'OEREB'

          feature.setAttribute('GPR_STATUS', gpr_status)
    PYTHONSYMBOL = processFeature
    -> AttributeRemover
AttributeRemover
    REMOVE_ATTRS = CODE,GEWUENSCHTES_WIPPENDATUM,GEWUENSCHTES_WIPPENDATUM.full,ID_GP_FALL,TITLE,ZEITSTAND_JAHR,ZEITSTAND_VERSION,GZS_JAHR,GZS_VERSION,UC_BEZEICHNUNG,UC_DMA
    -> TestFilter
Note: Testen auf ÖREB-Geoprodukt oder nicht. / Tasks für normale Geoprodukte werden / direkt in TB_TASK geschrieben. / Tasks von ÖREB-Geoprodukten werden ebenfalls in TB_TASK geschrieben. Zusätzlich wird jedoch die TASK_OBJECTID in die ÖREB-Tickettabelle geschrieben.
TestFilter
    DEFAULT_VALUE = NORMAL
    TEST_LIST = BOOL_OP,OR,COMPOSITE_TEST,<Unused>,TEST_CLAUSE,"TEST @Value(GPR_STATUS) = OEREB",OEREB
    OEREB -> SQLExecutor_2 [INITIATOR]
    NORMAL -> AttributeRemover_4
Note: Zugehörige Ticket-ID des ÖREB-Katasters ermitteln. In Frage kommen nur Tickets mit: / ART=4 (Aktualisierung mit Zeitstand) / STATUS=4 (freigegeben) / TASK_ID_GEODB is null (noch keine TASK_ID eingetragen)
SQLExecutor_2
    COMBINE_ATTRS = Keep Initiator Attributes if Conflict
    COMBINE_GEOM = Initiator Geometry Only
    DATASET = $(OEREB_DATABASE)
    EXPOSED_ATTRIBUTE_LIST = oereb_ticket_id
    FORMAT = POSTGRES
    POSTGRES_HOST = $(OEREB_HOST)
    POSTGRES_PASSWORD = $(OEREB_PASSWORD)
    POSTGRES_PORT = $(OEREB_PORT)
    POSTGRES_QUERY_FEATURE_TYPES_FOR_MERGE_FILTERS = Yes
    POSTGRES_READ_TIME_WITH_TIMEZONE = Yes
    POSTGRES_USER_NAME = $(OEREB_USERNAME)
    SQL_STATEMENT = SELECT t.id AS oereb_ticket_id FROM oereb.ticket t LEFT JOIN oereb.liefereinheit l ON t.liefereinheit = l.id LEFT JOIN workflow_gpr w ON l.workflow=w.workflow WHERE t.art=4 AND t.status=4 AND t.TASK_ID_GEODB IS NULL AND w.gprcode ='@Value(GPR_BEZEICHNUNG)'
    RESULT -> AttributeManager
    INITIATOR -> TestFilter_2
AttributeManager
    ATTR_TABLE:
      REMOVE GPR_BEZEICHNUNG
      REMOVE GZS_OBJECTID
      REMOVE TASK_STATUS
      REMOVE UC_OBJECTID
      RENAME_SET_VALUE TASK_OBJECTID > task_id_geodb
      REMOVE GPR_STATUS
      RENAME_SET_VALUE oereb_ticket_id > id
    -> ticket (writer POSTGRES_1)
ticket (writer POSTGRES_1)
    attributes: id serial,PrimaryKey, task_id_geodb int4
TestFilter_2
    DEFAULT_VALUE = TICKET_FOUND
    TEST_LIST = BOOL_OP,OR,COMPOSITE_TEST,<Unused>,TEST_CLAUSE,"TEST @Value(_matched_records) = 0",NO_TICKET
    NO_TICKET -> TestFilter_2_NO_TICKET
    TICKET_FOUND -> AttributeRemover_5
Note: Alle Tasks, für die kein ÖREB-Ticket gefunden wurde, werden hier geloggt.Sie werden auch nicht in TB_TASK geschrieben. Dies geschieht erst, wenn es ein dazugehöriges Ticket gibt.
TestFilter_2_NO_TICKET: Logger
    MAXCOORDS = 20
    MAXFEATS = 50
    MESSAGE = Für folgende Tasks konnte kein ÖREB-Ticket gefunden werden:
AttributeRemover_5
    REMOVE_ATTRS = GPR_BEZEICHNUNG,GPR_STATUS,_matched_records
    -> TB_TASK (writer ORACLE8I_DB_2)
AttributeRemover_4
    REMOVE_ATTRS = GPR_BEZEICHNUNG,GPR_STATUS
    -> TB_TASK (writer ORACLE8I_DB_2)
Note: insert tb_task from GeoDBprozess
TB_TASK (writer ORACLE8I_DB_2)
    attributes: TASK_OBJECTID number(38,0), GZS_OBJECTID number(38,0), UC_OBJECTID number(38,0), TASK_STATUS number(38,0)
